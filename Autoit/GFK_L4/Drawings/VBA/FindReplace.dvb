Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True
Sub replaceText()
    Dim acadApp As AcadApplication
    Dim acadDoc As AcadDocument
    Dim acadSelection As AcadSelectionSet
    Dim acadEntity As acadEntity
    Dim searchText As String
    Dim replaceText As String
    
    ' Get the search text from user input
    searchText = InputBox("Enter the search text:", "Search Text")
    If searchText = "" Then Exit Sub
    
    ' Get the replace text from user input
    replaceText = InputBox("Enter the replace text:", "Replace Text")
    
    ' Get the AutoCAD application
    Set acadApp = GetObject(, "AutoCAD.Application")
    
    ' Check if there is an active drawing
    If acadApp.Documents.Count = 0 Then
        MsgBox "No drawing is open.", vbExclamation
        Exit Sub
    End If
    
    ' Get the active drawing
    Set acadDoc = acadApp.ActiveDocument
    
    ' Create a selection set of all entities in the drawing
    Set acadSelection = acadDoc.SelectionSets.Add("MySelectionSet")
    acadSelection.Select acSelectionSetAll
    
    ' Loop through each selected entity
    For Each acadEntity In acadSelection
        ' Check if the entity is a text entity and contains the search text
        If TypeOf acadEntity Is AcadText And InStr(1, acadEntity.TextString, searchText) > 0 Then
            ' Replace the search text with the replace text
            acadEntity.TextString = Replace(acadEntity.TextString, searchText, replaceText)
        End If
    Next acadEntity
    
    ' Clear the selection set
    acadSelection.Clear
    
    ' Display a message to indicate completion
    MsgBox "Text replacement complete.", vbInformation
End Sub
